# -*- coding: utf-8 -*-
# Motýlí podnož – souměrná sestava ve velikostech S / M / L, spoj svar nebo šrouby.
#
# Oprava 10/2026: původní STEP měl křídla jen otočená o 180°, ne zrcadlená, a konce
# křídel 1 a 4 přečnívaly přes uzel. Tady se vezme křídlo +X −Y, (pro S a L) se
# vodorovně přepočítá kolem svého kořene u uzlu, posune se jen v ose Y tak, aby střed
# otisku jeho konců ležel na y = −30 mm, a zrcadlí se do všech čtyř poloh.
#
# Velikosti: křídlo se mění jen vodorovně (výška 728 mm, průřez jeklu 40×40×3 R6/R3,
# tloušťka výplně 5 mm a dosednutí na uzel zůstávají). Pokosy jeklů se přepočítají.
#   S  ~1300 mm (desky 160–180 × 90)   M  1533 mm (200 × 100)   L  ~1700 mm (220–240 × 100–110)
#
# Uzel: svařená krabička z plechů 6 mm (bočnice 120 × 94 a 108 × 94, víko 120 × 120),
# dole otevřená – zespodu přístup ke šroubům. Výška uzlu 110 mm (250–360), aby se do ní
# vešly konce strmějších jeklů velikosti S.
#   svar   – konce jeklů přímo na bočnici uzlu (x = ±60)
#   srouby – čelní deska 12 × 56 × 104 se 2 závity M10 (předvrt Ø8,5), v uzlu 2× Ø11;
#            šrouby M10 × 16 (8.8) zevnitř uzlu bez podložky
#
# Výstupy (assets/motyli-podnoz/): motyli_podnoz_<S|M|L>_<svar|srouby>.step,
# step_dily_<S|M|L>_<svar|srouby>.zip, kontrola_symetricka.json a pro web
# ../../motyli-podnoz-kridla.js (síť vzorového křídla pro každou velikost).
#
# Spuštění: freecadcmd / freecad.cmd vytvor_symetrickou_podnoz.FCMacro,
# nebo v konzoli FreeCADu exec(open(...).read()). Cesta k repu: proměnná ARKEAS93.
import os, json, re, shutil, tempfile, zipfile, math
import numpy as np
import FreeCAD as App
import Part
from FreeCAD import Vector as V


def repo_dir():
    env = os.environ.get('ARKEAS93')
    if env and os.path.isdir(env):
        return env
    try:
        here = os.path.dirname(os.path.abspath(__file__))
        if os.path.isfile(os.path.join(here, '..', 'motyli-podnoz.js')):
            return os.path.abspath(os.path.join(here, '..'))
    except NameError:
        pass
    return '/home/arkeas/src/arkeas93'


REPO = repo_dir()
SRC_STEP = os.path.join(REPO, 'assets', 'motyli-podnoz', 'motyli_podnoz.step')   # původní (nesouměrný) STEP, 33 těles
OUT_DIR = os.path.join(REPO, 'assets', 'motyli-podnoz')
JS_OUT = os.path.join(REPO, 'motyli-podnoz-kridla.js')

SIZES = [('S', 1300.0), ('M', None), ('L', 1700.0)]        # délka varianty svar; None = původní křídlo
SPOJE = ('svar', 'srouby')
HUB_HALF, HUB_T, HUB_Z0, HUB_Z1 = 60.0, 6.0, 250.0, 360.0   # uzel 120 × 120 × 110 pro všechny velikosti
PATCH_CENTER = 30.0
PLATE_T, PLATE_Y0, PLATE_Y1, PLATE_Z0, PLATE_Z1 = 12.0, 2.0, 58.0, 252.0, 356.0
BOLTS = [(42.0, 282.0), (18.0, 336.0)]          # (|y|, z) úhlopříčně
TAP_D, CLEAR_D = 8.5, 11.0
TOL_VOL = 1.0
MIN_MARGIN = 3.0

if not os.path.isfile(SRC_STEP):
    raise IOError('Nenalezen zdrojový STEP: ' + SRC_STEP)
solids = list(Part.read(SRC_STEP).Solids)
if len(solids) != 33:
    raise ValueError('Zdrojový STEP má %d těles, čekám 33' % len(solids))


def unit(v):
    o = V(v.x, v.y, v.z)
    if o.Length < 1e-9:
        raise ValueError('Nulový vektor')
    o.normalize()
    return o


def centre(s):
    b = s.BoundBox
    return V((b.XMin + b.XMax) / 2, (b.YMin + b.YMax) / 2, (b.ZMin + b.ZMax) / 2)


master = [s for s in solids if centre(s).x > 70 and centre(s).y < -20]
if len(master) != 8:
    raise ValueError('Vzorové křídlo +X −Y má %d těles, čekám 8' % len(master))
panel = max(master, key=lambda s: len(s.Faces))
top_plate = next(s for s in master if s.BoundBox.ZMin > 715)
tubes = [s for s in master if s is not panel and s is not top_plate]
if len(tubes) != 6:
    raise ValueError('Vzorové křídlo nemá 6 jeklů')


def faces_on_x(shape, x, tol=0.05):
    return [f for f in shape.Faces if abs(f.BoundBox.XMin - x) < tol and abs(f.BoundBox.XMax - x) < tol]


# ---- pořadí jeklů v obvodu křídla: 0 a 5 sedí na uzlu, 0 je horní ----
hub_tubes = sorted([t for t in tubes if faces_on_x(t, HUB_HALF)], key=lambda t: -centre(t).z)
if len(hub_tubes) != 2:
    raise ValueError('Na uzel musí dosedat 2 jekly, nalezeno %d' % len(hub_tubes))
adj = {id(a): [b for b in tubes if b is not a and a.distToShape(b)[0] < 0.05] for a in tubes}
ring = [hub_tubes[0]]
prev = hub_tubes[1]                      # první krok vede od dolního jeklu u uzlu pryč
while len(ring) < 6:
    nxt = [x for x in adj[id(ring[-1])] if x is not prev]
    if len(nxt) != 1:
        raise ValueError('Jekly křídla netvoří jednoduchý obvod')
    prev = ring[-1]
    ring.append(nxt[0])
if ring[5] is not hub_tubes[1]:
    raise ValueError('Obvod křídla nekončí na dolním jeklu u uzlu')


def axis_frame(shape):
    groups = []
    for face in shape.Faces:
        if 'Plane' not in str(type(face.Surface)) or face.Area < 200:
            continue
        n = unit(face.normalAt(0, 0))
        for g in groups:
            if abs(g[0].dot(n)) > 0.999:
                g[1] += face.Area
                break
        else:
            groups.append([n, face.Area])
    groups.sort(key=lambda g: -g[1])
    pairs = [(groups[i][1] + groups[j][1], groups[i][0], groups[j][0]) for i in range(len(groups)) for j in range(i + 1, len(groups)) if abs(groups[i][0].dot(groups[j][0])) < 0.05]
    pairs.sort(key=lambda p: -p[0])
    n1, n2 = pairs[0][1], pairs[0][2]
    axis = unit(n1.cross(n2))
    pts = np.array([[v.Point.x, v.Point.y, v.Point.z] for v in shape.Vertexes])
    a1 = pts @ np.array([n1.x, n1.y, n1.z]); a2 = pts @ np.array([n2.x, n2.y, n2.z])
    cog = shape.CenterOfMass
    rhs = np.array([(a1.max() + a1.min()) / 2, (a2.max() + a2.min()) / 2, axis.dot(V(cog.x, cog.y, cog.z))])
    xyz = np.linalg.solve(np.array([[n1.x, n1.y, n1.z], [n2.x, n2.y, n2.z], [axis.x, axis.y, axis.z]]), rhs)
    return axis, V(*[float(t) for t in xyz])


def line_intersection(a, b):
    u, p0 = a; v, q0 = b
    t = np.linalg.lstsq(np.column_stack(([u.x, u.y, u.z], [-v.x, -v.y, -v.z])), [q0.x - p0.x, q0.y - p0.y, q0.z - p0.z], rcond=None)[0]
    pa = p0 + u * float(t[0]); pb = q0 + v * float(t[1])
    if (pa - pb).Length > 8.0:
        raise ValueError('Osy sousedních jeklů se míjejí o %.3f mm' % (pa - pb).Length)
    return (pa + pb) * 0.5


FRAMES = [axis_frame(t) for t in ring]
NODES = [line_intersection(FRAMES[a], FRAMES[b]) for a, b in [(0, 5), (0, 1), (1, 2), (2, 3), (3, 4), (4, 5)]]
ROOT = NODES[0]


def rounded_profile(c, e1, e2, h, r):
    def pt(x, y):
        return c + e1 * x + e2 * y
    def ln(a, b):
        return Part.makeLine(pt(*a), pt(*b))
    def arc(a, b, cc, a0, a1):
        am = (a0 + a1) / 2
        return Part.Arc(pt(*a), pt(cc[0] + r * math.cos(am), cc[1] + r * math.sin(am)), pt(*b)).toShape()
    return Part.Wire([
        ln((-h + r, -h), (h - r, -h)), arc((h - r, -h), (h, -h + r), (h - r, -h + r), -math.pi / 2, 0),
        ln((h, -h + r), (h, h - r)), arc((h, h - r), (h - r, h), (h - r, h - r), 0, math.pi / 2),
        ln((h - r, h), (-h + r, h)), arc((-h + r, h), (-h, h - r), (-h + r, h - r), math.pi / 2, math.pi),
        ln((-h, h - r), (-h, -h + r)), arc((-h, -h + r), (-h + r, -h), (-h + r, -h + r), math.pi, 3 * math.pi / 2)])


def halfspace(point, normal):
    box = Part.makeBox(5000, 5000, 5000, V(-2500, -2500, -0.000001))
    box.Placement = App.Placement(point, App.Rotation(V(0, 0, 1), unit(normal)))
    return box


SEG = [(0, 1), (1, 2), (2, 3), (3, 4), (4, 5), (5, 0)]   # jekl i leží mezi uzly SEG[i]
RIM = 8.0                                                 # min. okraj výplně u jeklu (originál má 8 mm)


def fld(p, k):
    return V(ROOT.x + k * (p.x - ROOT.x), ROOT.y + k * (p.y - ROOT.y), p.z)


def tube_rebuild(i, k):
    """Jekl i znovu z os: pokosy v ose úhlu se sousedy, jekly u uzlu seříznuté rovinou x = 60.
    Ve všech spojích originálu je čistý pokos (ověřeno), při k = 1 vychází tvar přesně (odchylka < 0,001 mm)."""
    nodes = [fld(p, k) for p in NODES]
    a, b = SEG[i]; pa, pb = nodes[a], nodes[b]; ax = unit(pb - pa)
    e1 = PANEL_N; e2 = unit(ax.cross(e1))
    o = pa - ax * 200; L = (pb - pa).Length + 400
    t = Part.Face(rounded_profile(o, e1, e2, 20.0, 6.0)).extrude(ax * L).cut(Part.Face(rounded_profile(o, e1, e2, 17.0, 3.0)).extrude(ax * L))
    up = unit(nodes[SEG[(i - 1) % 6][1]] - nodes[SEG[(i - 1) % 6][0]])
    un = unit(nodes[SEG[(i + 1) % 6][1]] - nodes[SEG[(i + 1) % 6][0]])
    na = unit(ax + up); nb = unit(ax + un)
    t = t.common(halfspace(pa, na if na.dot(ax) > 0 else -na)).common(halfspace(pb, nb if nb.dot(ax) < 0 else -nb))
    if i in (0, 5):
        t = t.common(halfspace(V(HUB_HALF, 0, 0), V(1, 0, 0)))
    t = t.removeSplitter()
    if t.isNull() or len(t.Solids) != 1 or not t.isValid():
        raise ValueError('Neplatný jekl %d pro k = %.4f' % (i, k))
    return t.Solids[0]


pts = np.array([[v.Point.x, v.Point.y, v.Point.z] for v in panel.Vertexes])
vals, vecs = np.linalg.eigh(np.cov((pts - pts.mean(axis=0)).T))
_n = vecs[:, int(np.argmin(vals))]
PANEL_N = unit(V(float(_n[0]), float(_n[1]), 0))
_faces = sorted(panel.Faces, key=lambda f: -f.Area)
F0 = _faces[0]; NF = unit(F0.normalAt(0, 0))
THICK = abs((_faces[1].CenterOfMass - F0.CenterOfMass).dot(NF))
TV = unit(V(-PANEL_N.y, PANEL_N.x, 0)); ZZ = V(0, 0, 1)
PLANE_OFF = (F0.CenterOfMass - ROOT).dot(PANEL_N)


def to2(p):
    d = p - ROOT
    return (d.dot(TV), d.z)


def to3(u, w):
    return ROOT + TV * u + ZZ * w + PANEL_N * PLANE_OFF


def _axis2(j, k):
    nodes = [fld(p, k) for p in NODES]
    A = to2(nodes[SEG[j][0]]); B = to2(nodes[SEG[j][1]])
    ux, uy = B[0] - A[0], B[1] - A[1]; ul = math.hypot(ux, uy)
    return A, (ux / ul, uy / ul)


# hrany obrysu výplně: ke kterému jeklu patří a v jaké vzdálenosti od jeho osy leží
EDGE_TUBE = []
for e in F0.OuterWire.OrderedEdges:
    a2 = to2(e.Vertexes[0].Point); b2 = to2(e.Vertexes[-1].Point)
    m2 = ((a2[0] + b2[0]) / 2, (a2[1] + b2[1]) / 2)
    L = math.hypot(b2[0] - a2[0], b2[1] - a2[1]); d2 = ((b2[0] - a2[0]) / L, (b2[1] - a2[1]) / L)
    best = None
    for j in range(6):
        A, u = _axis2(j, 1.0)
        if abs(d2[0] * u[0] + d2[1] * u[1]) < 0.9999:
            continue
        sgn = (m2[0] - A[0]) * (-u[1]) + (m2[1] - A[1]) * u[0]
        if best is None or abs(sgn) < abs(best[1]):
            best = (j, sgn)
    if best is None:
        raise ValueError('Hrana výplně neleží podél žádného jeklu')
    EDGE_TUBE.append(best)


def panel_rebuild(k):
    """Výplň 5 mm: nový šestiúhelníkový obrys ve stejné vzdálenosti od os jeklů, otvory přepočtené
    vodorovně (k) a oříznuté tak, aby okraj u jeklu zůstal aspoň RIM."""
    lines = []
    for j, sgn in EDGE_TUBE:
        A, u = _axis2(j, k)
        lines.append(((A[0] - u[1] * sgn, A[1] + u[0] * sgn), u))
    def isect(l1, l2):
        (p, u), (q, v) = l1, l2
        t = ((q[0] - p[0]) * v[1] - (q[1] - p[1]) * v[0]) / (u[0] * v[1] - u[1] * v[0])
        return (p[0] + u[0] * t, p[1] + u[1] * t)
    pts2 = [isect(lines[i - 1], lines[i]) for i in range(len(lines))]
    outer = Part.makePolygon([to3(*p) for p in pts2] + [to3(*pts2[0])])
    M = None
    if abs(k - 1) > 1e-12:
        vs, sc = [PANEL_N, TV, ZZ], [1.0, k, 1.0]
        A = [[sum(sc[q] * vs[q][i] * vs[q][j] for q in range(3)) for j in range(3)] for i in range(3)]
        r = [ROOT.x, ROOT.y, ROOT.z]
        tr = [r[i] - sum(A[i][j] * r[j] for j in range(3)) for i in range(3)]
        M = App.Matrix(A[0][0], A[0][1], A[0][2], tr[0], A[1][0], A[1][1], A[1][2], tr[1], A[2][0], A[2][1], A[2][2], tr[2], 0, 0, 0, 1)
    full = Part.Face(outer); inset = full.makeOffset2D(-RIM)
    holes, clipped = [], 0
    for w in F0.Wires[1:]:
        hf = Part.Face(w if M is None else w.transformGeometry(M).Wires[0])
        c = hf.common(inset)
        if abs(c.Area - hf.Area) > 0.01:
            clipped += 1
        if c.Area > 1.0:
            holes.append(c)
    s = full.cut(Part.makeCompound(holes)).extrude(NF * (-THICK)).removeSplitter()
    if s.isNull() or len(s.Solids) != 1 or not s.isValid():
        raise ValueError('Neplatná výplň pro k = %.4f' % k)
    return s.Solids[0], outer, [f.OuterWire for h in holes for f in h.Faces], clipped


def bridges(outer, holes, step=0.5):
    """Nejužší můstek mezi otvory a nejužší okraj u jeklu (mm), vzorkováno po 0,5 mm."""
    from scipy.spatial import cKDTree
    def smp(w):
        return np.array([to2(p) for p in w.discretize(max(8, int(w.Length / step)))])
    S = [smp(h) for h in holes]; O = smp(outer)
    lab = np.concatenate([np.full(len(x), i) for i, x in enumerate(S)] + [np.full(len(O), -1)])
    P = np.concatenate(S + [O]); d, idx = cKDTree(P).query(P, k=40)
    best = rim = 1e9
    for r in range(len(P)):
        for dd, j in zip(d[r][1:], idx[r][1:]):
            if lab[j] != lab[r]:
                if lab[r] == -1 or lab[j] == -1:
                    rim = min(rim, dd)
                else:
                    best = min(best, dd)
                break
    return round(float(best), 2), round(float(rim), 2)


def wing(k):
    """Vzorové křídlo (+X −Y) pro vodorovný faktor k; vrací ([(název, tvar)], info o výplni)."""
    tubes_k = [tube_rebuild(i, k) for i in range(6)]
    panel_k, outer, holes, clipped = panel_rebuild(k)
    mid0 = (NODES[1] + NODES[2]) * 0.5; mid1 = (fld(NODES[1], k) + fld(NODES[2], k)) * 0.5
    plate_k = top_plate.copy(); plate_k.translate(mid1 - mid0)
    br, rim = bridges(outer, holes)
    info = {'mustek_min_mm': br, 'okraj_min_mm': rim, 'oriznute_otvory': clipped}
    return [('vypln_5mm', panel_k)] + [('jekl_40x40x3_%d' % (i + 1), t) for i, t in enumerate(tubes_k)] + [('horni_deska_110x86x8', plate_k)], info


def shift_y(parts):
    fs = [f for n, s in parts if n.startswith('jekl') for f in faces_on_x(s, HUB_HALF)]
    if not fs:
        raise ValueError('Žádný jekl nedosedá na čelo uzlu')
    return -PATCH_CENTER - (min(f.BoundBox.YMin for f in fs) + max(f.BoundBox.YMax for f in fs)) / 2.0


QUADS = [('kridlo_pX_mY', 1, 1), ('kridlo_pX_pY', 1, -1), ('kridlo_mX_pY', -1, -1), ('kridlo_mX_mY', -1, 1)]


def place(shape, sx, sy):
    s = shape.copy()
    if sy < 0:
        s = s.mirror(V(0, 0, 0), V(0, 1, 0))
    if sx < 0:
        s = s.mirror(V(0, 0, 0), V(1, 0, 0))
    return s


def hole_x(x0, length, y, z, d):
    return Part.makeCylinder(d / 2.0, length, V(x0, y, z), V(1, 0, 0))


def hub_parts(spoj):
    h, t, zt = HUB_HALF, HUB_T, HUB_Z1 - HUB_T
    px = Part.makeBox(t, 2 * h, zt - HUB_Z0, V(h - t, -h, HUB_Z0))
    if spoj == 'srouby':
        for sy in (1, -1):
            for by, bz in BOLTS:
                px = px.cut(hole_x(h - t - 1, t + 2, sy * -by, bz, CLEAR_D))
    py = Part.makeBox(2 * (h - t), t, zt - HUB_Z0, V(-h + t, h - t, HUB_Z0))
    return [('uzel_bocnice_pX_pl6', px), ('uzel_bocnice_mX_pl6', px.mirror(V(0, 0, 0), V(1, 0, 0))),
            ('uzel_bocnice_pY_pl6', py), ('uzel_bocnice_mY_pl6', py.mirror(V(0, 0, 0), V(0, 1, 0))),
            ('uzel_viko_pl6', Part.makeBox(2 * h, 2 * h, t, V(-h, -h, zt)))]


def end_plate():
    p = Part.makeBox(PLATE_T, PLATE_Y1 - PLATE_Y0, PLATE_Z1 - PLATE_Z0, V(HUB_HALF, -PLATE_Y1, PLATE_Z0))
    for by, bz in BOLTS:
        p = p.cut(hole_x(HUB_HALF - 1, PLATE_T + 2, -by, bz, TAP_D))
    return p


def assemble(wparts, sy_shift, spoj):
    dx = PLATE_T if spoj == 'srouby' else 0.0
    parts = [(n, s, 'uzel') for n, s in hub_parts(spoj)]
    for q, sx, sy in QUADS:
        for n, s in wparts:
            m = s.copy(); m.translate(V(dx, sy_shift, 0))
            parts.append((q + '_' + n, place(m, sx, sy), q))
        if spoj == 'srouby':
            parts.append((q + '_celni_deska_12x56x104_2xM10', place(end_plate(), sx, sy), q))
    return parts


def check(spoj, parts):
    rep = {'spoj': spoj, 'teles': len(parts), 'nevalidni': [], 'pruniky': []}
    for n, s, g in parts:
        if s.isNull() or not s.isValid() or len(s.Solids) != 1 or s.Volume <= 0:
            rep['nevalidni'].append(n)
    for i in range(len(parts)):
        for j in range(i + 1, len(parts)):
            ni, si, gi = parts[i]; nj, sj, gj = parts[j]
            if gi == gj or not si.BoundBox.intersect(sj.BoundBox):
                continue
            v = si.common(sj).Volume
            if v > TOL_VOL:
                rep['pruniky'].append([ni, nj, round(v, 3)])
    xf = HUB_HALF + (PLATE_T if spoj == 'srouby' else 0.0)
    fs = [f for n, s, g in parts if g == 'kridlo_pX_mY' and 'jekl' in n for f in faces_on_x(s, xf)]
    y0 = min(f.BoundBox.YMin for f in fs); y1 = max(f.BoundBox.YMax for f in fs)
    z0 = min(f.BoundBox.ZMin for f in fs); z1 = max(f.BoundBox.ZMax for f in fs)
    face = (-PLATE_Y1, -PLATE_Y0, PLATE_Z0, PLATE_Z1) if spoj == 'srouby' else (-HUB_HALF, HUB_HALF, HUB_Z0, HUB_Z1)
    margin = min(y0 - face[0], face[1] - y1, z0 - face[2], face[3] - z1)
    rep['otisk'] = {'y': [round(y0, 2), round(y1, 2)], 'z': [round(z0, 2), round(z1, 2)], 'okraj_mm': round(margin, 2), 'mezera_mezi_kridly_mm': round(-2 * y1, 2)}
    comp = Part.makeCompound([s for n, s, g in parts])
    b = comp.optimalBoundingBox()   # BoundBox je na rádiusech jeklů nafouknutý
    rep['obalka_mm'] = [round(b.XLength, 2), round(b.YLength, 2), round(b.ZLength, 2)]
    rep['z_min'] = round(b.ZMin, 3)
    rep['objem_mm3'] = round(comp.Volume, 1)
    rep['hmotnost_kg'] = round(comp.Volume * 7.85e-6, 2)
    rep['soumerna_obalka'] = abs(b.XMin + b.XMax) < 0.05 and abs(b.YMin + b.YMax) < 0.05
    rep['ok'] = not rep['nevalidni'] and not rep['pruniky'] and margin >= MIN_MARGIN and rep['soumerna_obalka'] and abs(b.ZMin) < 0.05
    return rep


def export(tag, parts, rep):
    import Import
    doc = App.newDocument('Motyli_' + tag)
    objs = []
    for n, s, g in parts:
        o = doc.addObject('Part::Feature', re.sub(r'[^A-Za-z0-9_]', '_', n)); o.Label = n; o.Shape = s; objs.append(o)
    doc.recompute()
    step = os.path.join(OUT_DIR, 'motyli_podnoz_%s.step' % tag)
    Import.export(objs, step)
    back = Part.read(step)
    rep['step_teles_po_nacteni'] = len(back.Solids)
    rep['step_validni'] = all(s.isValid() for s in back.Solids)
    tmp = tempfile.mkdtemp(prefix='motyli_%s_' % tag, dir=OUT_DIR)
    try:
        with zipfile.ZipFile(os.path.join(OUT_DIR, 'step_dily_%s.zip' % tag), 'w', zipfile.ZIP_DEFLATED) as zf:
            for i, o in enumerate(objs, 1):
                p = os.path.join(tmp, '%02d_%s.step' % (i, o.Label)); Import.export([o], p); zf.write(p, os.path.basename(p))
    finally:
        shutil.rmtree(tmp, ignore_errors=True)
    App.closeDocument(doc.Name)
    rep['soubory'] = ['assets/motyli-podnoz/motyli_podnoz_%s.step' % tag, 'assets/motyli-podnoz/step_dily_%s.zip' % tag]


def mesh_of(shape):
    import MeshPart   # tessellate() dává u výplně s 64 otvory ~95 000 bodů (17 MB JS), MeshPart ~7 000
    m = MeshPart.meshFromShape(Shape=shape, LinearDeflection=0.3, AngularDeflection=0.35, Relative=False)
    return {'verts': [[round(p.x, 1), round(p.y, 1), round(p.z, 1)] for p in m.Points], 'tris': [list(f.PointIndices) for f in m.Facets]}


# délka varianty svar ≈ 2·(kořen.x + k·(xmax − kořen.x)) → faktor k pro cílovou délku
def wing_xmax(k):
    nodes_k = [tube_rebuild(i, k) for i in range(6)]
    mid0 = (NODES[1] + NODES[2]) * 0.5; mid1 = (fld(NODES[1], k) + fld(NODES[2], k)) * 0.5
    pl = top_plate.copy(); pl.translate(mid1 - mid0)
    return Part.makeCompound(nodes_k + [pl]).optimalBoundingBox().XMax


def solve_k(target):
    """Faktor k tak, aby délka varianty svar byla přesně target (sečny, 0,1 mm)."""
    k0, k1 = 1.0, (target / 2.0 - ROOT.x) / (wing_xmax(1.0) - ROOT.x)
    f0 = 2 * wing_xmax(k0) - target
    for _ in range(8):
        f1 = 2 * wing_xmax(k1) - target
        if abs(f1) < 0.1:
            break
        k0, k1, f0 = k1, k1 - f1 * (k1 - k0) / (f1 - f0), f1
    return k1

report = {'zdroj': os.path.relpath(SRC_STEP, REPO), 'velikosti': {}}
js = {}
for size, target in SIZES:
    k = 1.0 if target is None else solve_k(target)
    wparts, pinfo = wing(k)
    sy = shift_y(wparts)
    srep = {'k': round(k, 5), 'shift_y_mm': round(sy, 3), 'vypln': pinfo, 'varianty': {}}
    print(size, 'k', round(k, 4), 'výplň', pinfo)
    for spoj in SPOJE:
        parts = assemble(wparts, sy, spoj)
        rep = check(spoj, parts)
        print(size, spoj, json.dumps(rep, ensure_ascii=False))
        if rep['ok']:
            export('%s_%s' % (size, spoj), parts, rep)
        srep['varianty'][spoj] = rep
    report['velikosti'][size] = srep
    js[size] = {'k': round(k, 5), 'shiftY': round(sy, 4), 'parts': [dict(name=n, **mesh_of(s)) for n, s in wparts]}

with open(os.path.join(OUT_DIR, 'kontrola_symetricka.json'), 'w', encoding='utf-8') as fh:
    json.dump(report, fh, ensure_ascii=False, indent=2)
with open(JS_OUT, 'w', encoding='utf-8') as fh:
    fh.write('/* Síť vzorového křídla motýlí podnože (+X −Y) pro velikosti S/M/L – generuje motyli-podnoz/vytvor_symetrickou_podnoz.FCMacro. */\n')
    fh.write('window.MOTYLI_KRIDLA=' + json.dumps(js, separators=(',', ':')) + ';\n')
ok = all(r['ok'] for s in report['velikosti'].values() for r in s['varianty'].values()) and all(s['vypln']['mustek_min_mm'] >= 6.0 and s['vypln']['okraj_min_mm'] >= RIM - 0.1 for s in report['velikosti'].values())
print('HOTOVO', 'OK' if ok else 'CHYBY – viz kontrola_symetricka.json')
